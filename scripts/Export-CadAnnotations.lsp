(defun jsonstring (value / result char)
 (setq result "\"")
 (foreach char (vl-string->list value)
  (setq result (strcat result (cond ((= char 34) "\\\"") ((= char 92) "\\\\") ((= char 10) "\\n") ((= char 13) "\\r") ((= char 9) "\\t") (t (chr char))))))
 (strcat result "\""))
(defun numberstr (value) (rtos (if value value 0.0) 2 12))
(defun xyzjson (value) (strcat "[" (numberstr (car value)) "," (numberstr (cadr value)) "," (numberstr (caddr value)) "]"))
(setq output (open "OUTPUT_PATH" "w"))
(write-line (strcat "{\"SourceName\":" (jsonstring "SOURCE_NAME") ",\"Blocks\":[") output)
(setq selected (ssget "_X" '((0 . "INSERT") (410 . "Model"))) firstblock T index 0)
(if selected
 (repeat (sslength selected)
  (setq entity (ssname selected index) data (entget entity) attrs nil)
  (if (= 1 (cdr (assoc 66 data)))
   (progn
    (setq att (entnext entity))
    (while (and att (= "ATTRIB" (cdr (assoc 0 (entget att)))))
     (setq attr (entget att))
     (if (= 0 (logand 1 (cdr (assoc 70 attr)))) (setq attrs (cons attr attrs)))
     (setq att (entnext att)))))
  (if attrs
   (progn
    (if (not firstblock) (write-line "," output)) (setq firstblock nil)
    (write-line (strcat "{\"Layer\":" (jsonstring (cdr (assoc 8 data))) ",\"Origin\":" (xyzjson (cdr (assoc 10 data))) ",\"Texts\":[") output)
    (setq firsttext T)
    (foreach attr (reverse attrs)
     (if (not firsttext) (write-line "," output)) (setq firsttext nil)
     (setq aligned (or (/= 0 (cdr (assoc 72 attr))) (/= 0 (cdr (assoc 74 attr)))))
     (setq anchor (cdr (assoc (if aligned 11 10) attr)))
     (write-line (strcat "{\"Value\":" (jsonstring (cdr (assoc 1 attr))) ",\"Anchor\":" (xyzjson anchor) ",\"Height\":" (numberstr (cdr (assoc 40 attr))) ",\"Centered\":" (if aligned "true" "false") "}") output))
    (write-line "]}" output)))
  (setq index (1+ index))))
(write-line "]}" output) (close output) (princ)
